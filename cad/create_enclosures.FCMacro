# Dual-Auth Cafe Sentry — parametric enclosure and component-envelope generator
# Run inside FreeCAD 0.21+ (PartDesign primitives are native editable features).
# All dimensions are millimetres. Reference envelopes are DRAFT, not fit/RF/
# thermal/acoustic/battery-safety validation. See cad/README.md before use.
import FreeCAD as App
import Part
import PartDesign
import Mesh
import os

OUT = os.path.join(os.path.expanduser("~"), "DualAuthCafeSentry-CAD")
if not os.path.isdir(OUT):
    os.makedirs(OUT)

def add_ref_box(doc, name, label, length, width, height, x, y, z, note):
    obj = doc.addObject("Part::Box", name)
    obj.Label = label
    obj.Length = length
    obj.Width = width
    obj.Height = height
    obj.Placement = App.Placement(App.Vector(x, y, z), App.Rotation())
    obj.addProperty("App::PropertyString", "DesignStatus", "Project")
    obj.addProperty("App::PropertyString", "EvidenceNote", "Project")
    obj.DesignStatus = "DRAFT REFERENCE ENVELOPE — not a released component"
    obj.EvidenceNote = note
    obj.ViewObject.Transparency = 72
    return obj

def add_ref_cylinder(doc, name, label, radius, height, x, y, z, note):
    obj = doc.addObject("Part::Cylinder", name)
    obj.Label = label
    obj.Radius = radius
    obj.Height = height
    obj.Placement = App.Placement(App.Vector(x, y, z), App.Rotation())
    obj.addProperty("App::PropertyString", "DesignStatus", "Project")
    obj.addProperty("App::PropertyString", "EvidenceNote", "Project")
    obj.DesignStatus = "DRAFT REFERENCE ENVELOPE — not a released component"
    obj.EvidenceNote = note
    obj.ViewObject.Transparency = 68
    return obj

def add_parametric_case(doc, prefix, outer_l, outer_w, outer_h, wall, base, lid_t):
    lower_h = outer_h - lid_t
    shell_body = doc.addObject("PartDesign::Body", prefix + "LowerShellBody")
    shell_body.Label = prefix + " lower shell — parametric Part Design"
    outer = doc.addObject("PartDesign::AdditiveBox", prefix + "OuterBlank")
    shell_body.addObject(outer)
    outer.Label = "Outer blank"
    outer.Length, outer.Width, outer.Height = outer_l, outer_w, lower_h
    outer.Placement = App.Placement(App.Vector(0, 0, 0), App.Rotation())
    doc.recompute()

    cavity = doc.addObject("PartDesign::SubtractiveBox", prefix + "InteriorCavity")
    shell_body.addObject(cavity)
    cavity.Label = "Interior cavity — wall and base allowance"
    cavity.Length = outer_l - 2 * wall
    cavity.Width = outer_w - 2 * wall
    cavity.Height = lower_h - base + 0.2
    cavity.Placement = App.Placement(App.Vector(wall, wall, base), App.Rotation())
    doc.recompute()

    lid_body = doc.addObject("PartDesign::Body", prefix + "LidBody")
    lid_body.Label = prefix + " lid — parametric Part Design"
    lid = doc.addObject("PartDesign::AdditiveBox", prefix + "Lid")
    lid_body.addObject(lid)
    lid.Label = "Lid blank"
    lid.Length, lid.Width, lid.Height = outer_l, outer_w, lid_t
    lid.Placement = App.Placement(App.Vector(0, 0, lower_h), App.Rotation())
    doc.recompute()

    for obj in (shell_body, lid_body):
        obj.addProperty("App::PropertyString", "DesignStatus", "Project")
        obj.DesignStatus = "DRAFT — joint, bosses, tolerances, material and fit not resolved"
    for obj in (outer, cavity, lid):
        obj.Visibility = False
    return shell_body, lid_body


def add_cutout_box(doc, body, name, label, length, width, height, x, y, z, note):
    obj = doc.addObject("PartDesign::SubtractiveBox", name)
    body.addObject(obj)
    obj.Label = label
    obj.Length = length
    obj.Width = width
    obj.Height = height
    obj.Placement = App.Placement(App.Vector(x, y, z), App.Rotation())
    obj.addProperty("App::PropertyString", "DesignStatus", "Project")
    obj.addProperty("App::PropertyString", "EvidenceNote", "Project")
    obj.DesignStatus = "DRAFT CUTOUT — dimensions require physical connector check"
    obj.EvidenceNote = note
    doc.recompute()
    return obj

def export_doc(doc, enclosure_objects, reference_objects, prefix):
    doc.recompute()
    fcstd = os.path.join(OUT, prefix + ".FCStd")
    step = os.path.join(OUT, prefix + "_enclosure.step")
    stl = os.path.join(OUT, prefix + "_enclosure.stl")
    asm_step = os.path.join(OUT, prefix + "_assembly_reference.step")
    asm_stl = os.path.join(OUT, prefix + "_assembly_reference.stl")
    doc.saveAs(fcstd)
    Part.export(enclosure_objects, step)
    Mesh.export(enclosure_objects, stl)
    assembly_objects = list(enclosure_objects) + list(reference_objects)
    Part.export(assembly_objects, asm_step)
    Mesh.export(assembly_objects, asm_stl)
    print("Saved " + fcstd)
    print("Exported enclosure-only: " + step + " and " + stl)
    print("Exported reference assembly: " + asm_step + " and " + asm_stl)

def make_pod():
    # Larger packaging study envelope. The earlier 55 x 30 x 19.7 mm
    # was only the protected-cell-to-NFC-coil stack lower bound.
    doc = App.newDocument("SentryPod")
    shell, lid = add_parametric_case(doc, "Pod", 72.0, 34.0, 29.0, 1.5, 1.5, 1.5)
    refs = []

    refs.append(add_ref_box(doc, "PodCarrierPcb", "Pod carrier PCB — 49.5 x 28 x 1.6",
                49.5, 28.0, 1.6, 10.0, 3.0, 8.0,
                "Packaging-study placement only. The current KiCad Pod PCB is still outline-only; dimensions and placement are not yet released."))
    add_cutout_box(doc, shell, "PodUsbCutout", "S3-Zero USB-C case-wall cutout — draft",
                   10.0, 1.7, 4.8, 14.0, -0.1, 9.0,
                   "Provisional top-wall opening centred on the upright S3-Zero USB connector. Check the actual connector shell, insertion angle and case tolerance.")

    refs.append(add_ref_box(doc, "PodBatteryReference", "Renata ICP521630PM-01 protected-pack candidate",
                31.5, 17.0, 5.7, 2.5, 6.5, 1.5,
                "Candidate maximum envelope only: 31.5 x 17.0 x 5.7 mm. Protection thresholds, charge-voltage tolerance, NTC, wire length, connector, restraint and swelling allowance remain unresolved."))

    refs.append(add_ref_box(doc, "PodS3ZeroModule", "Waveshare ESP32-S3-Zero module envelope",
                18.0, 23.5, 1.2, 10.0, 3.25, 9.6,
                "Public 18 x 23.5 mm board outline, upright with USB at the top and antenna at the bottom. Castellated land dimensions and connector details must be checked against the received revision."))

    refs.append(add_ref_box(doc, "PodS3AntennaKeepout", "S3-Zero antenna keepout / carrier relief",
                8.0, 3.5, 0.35, 15.0, 23.5, 9.6,
                "Assumed ceramic antenna region at the module's bottom end. The carrier PCB notch and battery edge align to this placeholder; verify the actual antenna dimensions before release."))
    refs.append(add_ref_box(doc, "PodS3UsbEnvelope", "S3-Zero USB-C connector access envelope",
                10.0, 5.0, 3.5, 14.0, 0.5, 9.6,
                "Approximate connector/access envelope. The case requires a top-wall USB cutout; verify actual connector shell and plug insertion."))

    refs.append(add_ref_box(doc, "PodImuModule", "Adafruit 3886 IMU breakout envelope",
                26.0, 17.8, 4.6, 33.5, 8.1, 9.6,
                "Published 26 x 17.8 x 4.6 mm envelope. Candidate only; product was out of stock in the latest register check and its board drawing/schematic have not been inspected."))

    refs.append(add_ref_box(doc, "PodNfcModule", "Elechouse PN5321 MINI module envelope — stacked above IMU",
                25.0, 16.4, 4.4, 34.5, 14.0, 15.0,
                "Published 25 x 16.4 x 4.4 mm candidate envelope stacked above the Adafruit 3886 breakout, shifted toward the lower board edge to clear its 1x6 header and STEMMA QT connector. Provide a spacer/bracket and check host cable access, antenna cable routing and lid clearance."))

    refs.append(add_ref_box(doc, "PodNfcAntennaReference", "PN532 antenna placeholder / RF keepout",
                25.0, 10.0, 1.0, 44.5, 12.0, 26.0,
                "10 x 25 mm antenna candidate oriented lengthwise. This placement gives 10.5 mm horizontal separation from the battery end and >10 mm from the piezo reference. Exact antenna thickness, cable and manufacturer keepout remain unknown."))

    refs.append(add_ref_cylinder(doc, "PodPiezoReference", "CPT-2475-92T 24 mm piezo reference envelope",
                     12.0, 7.5, 20.0, 15.0, 17.0,
                     "24 mm diameter x 7.5 mm high. Published rating is 92 dB minimum at 10 cm, not the 105 dB target. This is a packaging reference only; sound cavity, vent and acoustic output are not validated."))

    export_doc(doc, [shell, lid], refs, "SentryPod")
    return doc

def make_keyfob():
    # Revised mechanical evaluation layout: upright C3-Zero, antenna relief,
    # accessible USB edge, and motor/battery separated laterally.
    doc = App.newDocument("PocketKeyfob")
    shell, lid = add_parametric_case(doc, "Keyfob", 44.0, 30.0, 15.5, 1.5, 1.5, 1.5)
    refs = []

    # Carrier board: 37 x 25 x 1.6 mm, 1 mm nominal clearance in the case cavity.
    refs.append(add_ref_box(doc, "KeyfobCarrierPcb", "Keyfob carrier PCB — 37 x 25 x 1.6",
                37.0, 25.0, 1.6, 2.5, 2.5, 7.0,
                "Matches the current KiCad outline with an 8 x 3.5 mm antenna relief notch. Stack-up, copper clearance, notch strength and enclosure tolerance remain unverified."))

    # C3-Zero is now upright: 18 mm wide x 23.5 mm long, USB at the top end.
    refs.append(add_ref_box(doc, "C3ZeroModule", "Waveshare ESP32-C3-Zero module envelope",
                18.0, 23.5, 1.2, 12.0, 3.75, 8.6,
                "Public 18 x 23.5 mm outline. Upright placement matches the revised carrier footprint. Castellated pad dimensions, USB shell details and actual antenna keepout still require inspection."))

    refs.append(add_ref_box(doc, "C3AntennaKeepout", "C3-Zero antenna relief / no-battery zone",
                8.0, 3.5, 0.35, 17.0, 24.0, 8.6,
                "Matches the provisional carrier-board notch. Waveshare antenna region is at the module end in this orientation; exact dimensions and required RF clearance must be checked against the actual board."))

    refs.append(add_ref_box(doc, "C3UsbEnvelope", "C3-Zero USB-C connector access envelope",
                10.0, 5.0, 3.5, 16.0, 0.5, 8.6,
                "Approximate visual envelope centred on the module USB edge. The lower-shell top-wall cutout is 10 x 4.8 mm; verify connector shell, plug access, insertion angle and case tolerances."))

    # Cut through the top wall to expose the module USB-C connector.
    add_cutout_box(doc, shell, "KeyfobUsbCutout", "USB-C access cutout — draft 10 x 4.8",
                   10.0, 1.7, 4.8, 16.0, -0.1, 8.0,
                   "Provisional opening through the y=0 case wall. Position is based on upright module placement, not a dimensioned USB connector drawing.")

    # Candidate protected pack envelope; leads and connector are not modelled.
    refs.append(add_ref_box(doc, "KeyfobBatteryReference", "Renata ICP402025PC-01 protected-pack candidate",
                27.5, 20.5, 4.3, 2.0, 3.5, 1.5,
                "Candidate maximum envelope only: 27.5 x 20.5 x 4.3 mm. Pack connector, lead exit, adhesive, insulation, swelling allowance and actual vendor drawing must be checked. Not a final battery selection."))

    # Motor at PCB local (33,5), translated by carrier origin (2.5,2.5).
    refs.append(add_ref_cylinder(doc, "KeyfobMotorReference", "Vybronics VCLP1020B002L evaluation motor",
                     5.0, 2.1, 35.5, 7.5, 8.75,
                     "10 mm diameter x 2.1 mm body; 3 V nominal, 2.5–3.5 V operating, 30 mA max rated current, 80 mA max start current, 0.75 G minimum at 3 V, 25 mm leads. Evaluation candidate only; verify actual haptic feel, lead routing and adhesive retention. Precision Microdrives 308-100 remains a smaller 8 mm alternate. The VCLP datasheet also specifies 9.0 mm diameter x 0.15 mm double-sided tape; full lead-exit envelope remains to be checked."))

    refs.append(add_ref_cylinder(doc, "KeyfobMotorTapeReference", "VCLP1020B002L adhesive tape reference",
                     4.5, 0.15, 35.5, 7.5, 8.6,
                     "Nominal 9.0 mm diameter x 0.15 mm double-sided tape from motor datasheet. Adhesive thickness/placement and case coupling are not validated."))

    # Top-side component envelopes translated from the revised PCB positions.
    refs.append(add_ref_box(doc, "KeyfobQ1Envelope", "Q1 IRLML6344 SOT-23 envelope",
                2.9, 2.5, 1.2, 30.55, 20.45, 8.6,
                "Approximate package envelope at PCB local (29.5,19.2)."))
    refs.append(add_ref_box(doc, "KeyfobD1Envelope", "D1 PMEG2010AEB SOD-523 envelope",
                1.6, 1.0, 0.65, 34.7, 21.2, 8.6,
                "Approximate package envelope at PCB local (33,19.2); verify manufacturer land pattern."))
    refs.append(add_ref_box(doc, "KeyfobR1Envelope", "R1 0603 gate resistor envelope",
                1.6, 0.8, 0.6, 31.2, 24.1, 8.6,
                "Approximate 0603 body envelope at PCB local (29.5,22)."))
    refs.append(add_ref_box(doc, "KeyfobR2Envelope", "R2 0603 gate pull-down envelope",
                1.6, 0.8, 0.6, 34.2, 24.1, 8.6,
                "Approximate 0603 body envelope at PCB local (32.5,22)."))
    refs.append(add_ref_box(doc, "KeyfobC1Envelope", "C1 0603 local bypass envelope",
                1.6, 0.8, 0.8, 30.7, 13.6, 8.6,
                "Approximate 0603 body envelope at PCB local (29,11.5)."))
    refs.append(add_ref_box(doc, "KeyfobC2Envelope", "C2 0805 local reservoir envelope",
                2.0, 1.25, 1.0, 34.0, 13.375, 8.6,
                "Approximate 0805 body envelope at PCB local (32.5,11.5)."))
    refs.append(add_ref_box(doc, "KeyfobMotorConnectorEnvelope", "J1 motor wire solder-pad region",
                4.8, 3.6, 0.5, 32.1, 16.2, 8.6,
                "Draft wire-pad region at PCB local (32,15.5); lead strain relief and routing are not modelled."))

    export_doc(doc, [shell, lid], refs, "PocketKeyfob")
    return doc

pod_doc = make_pod()
keyfob_doc = make_keyfob()

print("DRAFT parametric enclosure documents and reference assemblies saved to " + OUT)
print("Pod outside envelope: 72 x 34 x 29 mm (packaging-study envelope; not final approval).")
print("Keyfob outside envelope: 44 x 30 x 15.5 mm (revised provisional layout).")
print("Keyfob carrier concept: 37 x 25 x 1.6 mm with a provisional antenna relief notch; module, motor, USB and passives are reference envelopes only.")
print("FreeCAD geometry has not been run or validated in this execution environment.")
